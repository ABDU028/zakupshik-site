;;; ============================================================
;;; ОБМЕР v3 - Дизайн 3D Квартир
;;; Рисуешь КОМНАТЫ (как меряешь - изнутри), двери/окна, стояки.
;;; Стены программа строит сама: команда SST.
;;; Загрузка: _APPLOAD -> этот файл -> Загрузить (и в «Автозагрузку»).
;;; Пробел/Enter после команды - повторить её (следующая комната и т. п.).
;;; ============================================================
(vl-load-com)
(if (not obm:ext) (setq obm:ext 300))     ; наружные стены, мм (условно)

;;; ---------- служебное ----------
(defun obm:layer (n c lw / e)
  (if (tblsearch "LAYER" n)
    (progn (setq e (entget (tblobjname "LAYER" n)))
           (setq e (subst (cons 62 c) (assoc 62 e) e))
           (if (assoc 370 e) (setq e (subst (cons 370 lw) (assoc 370 e) e)) (setq e (append e (list (cons 370 lw)))))
           (entmod e))
    (entmake (list '(0 . "LAYER") '(100 . "AcDbSymbolTableRecord") '(100 . "AcDbLayerTableRecord")
                   (cons 2 n) '(70 . 0) (cons 62 c) '(6 . "Continuous") (cons 370 lw)))))
(defun obm:style () (if (tblsearch "STYLE" "OBMER") "OBMER" "Standard"))
(defun obm:p (x y) (list x y 0.0))
(defun obm:rect (p1 p2 lay / x1 x2 y1 y2)
  (setq x1 (min (car p1) (car p2)) x2 (max (car p1) (car p2)) y1 (min (cadr p1) (cadr p2)) y2 (max (cadr p1) (cadr p2)))
  (entmake (list '(0 . "LWPOLYLINE") '(100 . "AcDbEntity") (cons 8 lay) '(100 . "AcDbPolyline") '(90 . 4) '(70 . 1)
                 (list 10 x1 y1) (list 10 x2 y1) (list 10 x2 y2) (list 10 x1 y2))))
(defun obm:line (a b lay) (entmake (list '(0 . "LINE") (cons 8 lay) (cons 10 a) (cons 11 b))))
(defun obm:circle (c r lay) (entmake (list '(0 . "CIRCLE") (cons 8 lay) (cons 10 c) (cons 40 r))))
(defun obm:arc (c r a1 a2 lay) (entmake (list '(0 . "ARC") (cons 8 lay) (cons 10 c) (cons 40 r) (cons 50 a1) (cons 51 a2))))
(defun obm:text (pt h s rot lay)
  (entmake (list '(0 . "TEXT") (cons 8 lay) (cons 7 (obm:style)) (cons 10 pt) (cons 11 pt) (cons 40 h) (cons 1 s) (cons 50 rot) '(72 . 1) '(73 . 2))))
(defun obm:askint (msg def / v) (setq v (getint (strcat "\n" msg " <" (itoa def) ">: "))) (if v v def))
(defun obm:askstr (msg def / v) (setq v (getstring T (strcat "\n" msg " <" def ">: "))) (if (= v "") def v))

;; точка: клик, или Enter - «от угла»: клик по углу + отступы
(defun obm:start (msg / p b dx dy)
  (setq p (getpoint (strcat "\n" msg " - клик, или Enter = отступом от угла: ")))
  (if (not p)
    (progn
      (setq b (getpoint "\nКликни УГОЛ, от которого меряешь (курсор прилипнет): "))
      (if b (progn
        (setq dx (getreal "\nОтступ по горизонтали, мм (вправо +, влево -) <0>: ")) (if (not dx) (setq dx 0.0))
        (setq dy (getreal "\nОтступ по вертикали, мм (вверх +, вниз -) <0>: ")) (if (not dy) (setq dy 0.0))
        (setq p (obm:p (+ (car b) dx) (+ (cadr b) dy)))))))
  p)
(defun obm:corners (msg / p1 p2)
  (if (setq p1 (obm:start (strcat msg ", первый угол")))
    (progn (setvar "LASTPOINT" p1)
           (setq p2 (getcorner p1 "\nВторой угол: введи @ширина,высота (влево/вниз - с минусом), например @3450,5750: "))))
  (if (and p1 p2) (list p1 p2)))
(defun obm:info (p1 p2 / x1 x2 y1 y2 hor)
  (setq x1 (min (car p1) (car p2)) x2 (max (car p1) (car p2)) y1 (min (cadr p1) (cadr p2)) y2 (max (cadr p1) (cadr p2)))
  (setq hor (>= (- x2 x1) (- y2 y1)))
  (list x1 y1 x2 y2 hor (if hor (- x2 x1) (- y2 y1)) (if hor (- y2 y1) (- x2 x1)) (obm:p (/ (+ x1 x2) 2.0) (/ (+ y1 y2) 2.0))))
(defun obm:label (inf s side lay / hor th c)
  (setq hor (nth 4 inf) th (nth 6 inf) c (nth 7 inf))
  (if hor (obm:text (obm:p (car c) (+ (cadr c) (* side (+ (/ th 2.0) 230)))) 140 s 0.0 lay)
          (obm:text (obm:p (+ (car c) (* side (+ (/ th 2.0) 230))) (cadr c)) 140 s (/ pi 2) lay)))
(defun obm:centroid (e / pts n sx sy)
  (setq pts (vl-remove-if-not '(lambda (x) (= (car x) 10)) (entget e)) n (length pts) sx 0.0 sy 0.0)
  (foreach p pts (setq sx (+ sx (cadr p)) sy (+ sy (caddr p))))
  (obm:p (/ sx n) (/ sy n)))
(defun obm:area (e) (vla-get-Area (vlax-ename->vla-object e)))

;;; ---------- НАСТРОЙКА ----------
(defun c:NASTROYKA (/ ce ss i)
  (setq ce (getvar "CMDECHO")) (setvar "CMDECHO" 0)
  (setvar "INSUNITS" 4) (setvar "MEASUREMENT" 1) (setvar "MEASUREINIT" 1)
  (setvar "LUNITS" 2) (setvar "LUPREC" 0) (setvar "AUNITS" 0) (setvar "AUPREC" 0)
  (setvar "OSMODE" 167) (setvar "AUTOSNAP" 63) (setvar "ORTHOMODE" 1) (setvar "DYNMODE" 3)
  (setvar "PICKFIRST" 1) (setvar "MIRRTEXT" 0) (setvar "LTSCALE" 50)
  (foreach L '(("КОМНАТЫ" 7 35) ("СТЕНЫ-АВТО" 7 50) ("СТЕНЫ" 7 50) ("ОКНА" 5 25) ("ДВЕРИ" 6 25) ("СТОЯКИ" 4 25)
               ("ЩИТОК" 1 25) ("ВЕНТ" 8 25) ("РАДИАТОРЫ" 30 25) ("ПОМЕЩЕНИЯ" 2 18) ("РАЗМЕРЫ" 3 18))
    (obm:layer (car L) (cadr L) (caddr L)))
  (setvar "LWDISPLAY" 1)
  (if (not (tblsearch "STYLE" "OBMER"))
    (entmake '((0 . "STYLE") (100 . "AcDbSymbolTableRecord") (100 . "AcDbTextStyleTableRecord")
               (2 . "OBMER") (70 . 0) (40 . 0.0) (41 . 1.0) (50 . 0.0) (71 . 0) (42 . 150.0) (3 . "arial.ttf") (4 . ""))))
  (setvar "TEXTSTYLE" (obm:style)) (setvar "TEXTSIZE" 150)
  (setvar "DIMSCALE" 1) (setvar "DIMTXT" 150) (setvar "DIMTXSTY" (obm:style))
  (setvar "DIMTSZ" 100) (setvar "DIMASZ" 100) (setvar "DIMEXE" 100) (setvar "DIMEXO" 100)
  (setvar "DIMDLE" 100) (setvar "DIMGAP" 50) (setvar "DIMTAD" 1) (setvar "DIMTIH" 0) (setvar "DIMTOH" 0)
  (setvar "DIMDEC" 0) (setvar "DIMLUNIT" 2) (setvar "DIMZIN" 8) (setvar "DIMCLRD" 256) (setvar "DIMCLRE" 256) (setvar "DIMCLRT" 256)
  (if (tblsearch "DIMSTYLE" "OBMER") (command "_.-DIMSTYLE" "_S" "OBMER" "_Y") (command "_.-DIMSTYLE" "_S" "OBMER"))
  (if (getvar "DIMLAYER") (setvar "DIMLAYER" "РАЗМЕРЫ"))
;; выноски: масштаб 40 (текст ~160 мм, стрелка ~160 мм в натуре); уже поставленные - тоже
  (if (getvar "MLEADERSCALE") (setvar "MLEADERSCALE" 40))
  (if (setq ss (ssget "_X" '((0 . "MULTILEADER"))))
    (progn (setq i 0) (repeat (sslength ss) (vl-catch-all-apply 'vla-put-ScaleFactor (list (vlax-ename->vla-object (ssname ss i)) 40)) (setq i (1+ i)))))
  ;; все уже поставленные размеры - на наш стиль (крупные, засечки, цифры вдоль линии)
  (if (setq ss (ssget "_X" '((0 . "DIMENSION")))) (command "_.-DIMSTYLE" "_A" ss ""))
  (setvar "CLAYER" "КОМНАТЫ")
  (setvar "CMDECHO" ce)
  (princ))

;;; ---------- 1. КОМНАТЫ ----------
(defun obm:roomname (e / c n h)
  (setq c (obm:centroid e))
  (setq n (obm:askstr "Название комнаты" "Комната"))
  (setq h (obm:askint "Высота потолка, мм" 2700))
  (obm:text c 250 n 0.0 "ПОМЕЩЕНИЯ")
  (obm:text (obm:p (car c) (- (cadr c) 350)) 170 (strcat "Потолок " (itoa h)) 0.0 "ПОМЕЩЕНИЯ")
  (obm:text (obm:p (car c) (- (cadr c) 650)) 150 (strcat (rtos (/ (obm:area e) 1e6) 2 1) " м2") 0.0 "ПОМЕЩЕНИЯ"))

;; KOM - прямоугольная комната: угол + @длина,ширина
(defun c:KOM (/ r)
  (setvar "CLAYER" "КОМНАТЫ")
  (if (setq r (obm:corners "Комната"))
    (progn (obm:rect (car r) (cadr r) "КОМНАТЫ") (obm:roomname (entlast))))
  (princ))

;; KMT - комната кликом: рисуешь стены обычными линиями, потом кликаешь ВНУТРИ комнаты -
;; контур строится сам по твоим линиям (столбы внутри не мешают), потом название и высота
(defun c:KMT (/ p before ss i e best ba a ce)
  (setq ce (getvar "CMDECHO")) (setvar "CMDECHO" 0)
  (if (getvar "HPBOUND") (setvar "HPBOUND" 1))
  (while (setq p (getpoint "\nКликни ВНУТРИ комнаты (Enter - закончить): "))
    (setq before (entlast))
    (command "_.-BOUNDARY" p "")
    (setq e (if before (entnext before) (entnext)) best nil ba 0.0 ss '())
    (while e
      (if (= (cdr (assoc 0 (entget e))) "LWPOLYLINE")
        (progn (setq ss (cons e ss) a (obm:area e)) (if (> a ba) (setq ba a best e))))
      (setq e (entnext e)))
    (foreach x ss (if (/= x best) (entdel x)))
    (if best
      (progn
        (vla-put-Layer (vlax-ename->vla-object best) "КОМНАТЫ")
        (obm:roomname best))
      (princ "\nКонтур не найден: проверь, что стены комнаты сомкнуты без щелей (линии сходятся в углах).")))
  (setvar "CMDECHO" ce)
  (princ))

;; KOMF - комната любой формы: обходишь стены по углам
(defun c:KOMF (/ p e)
  (setvar "CLAYER" "КОМНАТЫ")
  (if (setq p (obm:start "Комната любой формы, первый угол"))
    (progn
      (princ "\nОбходи комнату по углам: мышкой направление, длину цифрами, Enter. В конце З (или C) - замкнуть.")
      (command "_.PLINE" p)
      (while (> (getvar "CMDACTIVE") 0) (command pause))
      (setq e (entlast))
      (if (and e (= (cdr (assoc 0 (entget e))) "LWPOLYLINE")) (obm:roomname e))))
  (princ))

;;; ---------- 1б. СТОЛБЫ / КОЛОННЫ / ВЫСТУПЫ (монолит внутри комнаты) ----------
(defun obm:hatch (e pat / ce)
  (setq ce (getvar "CMDECHO")) (setvar "CMDECHO" 0)
  (vl-catch-all-apply 'command (list "_.-HATCH" "_P" pat 25 0 "_S" e "" ""))
  (setvar "CMDECHO" ce))
;; KOL - прямоугольный столб: Enter -> угол комнаты -> отступы -> @ширина,глубина
(defun c:KOL (/ r)
  (setvar "CLAYER" "СТЕНЫ")
  (if (setq r (obm:corners "Столб / колонна"))
    (progn (obm:rect (car r) (cadr r) "СТЕНЫ") (obm:hatch (entlast) "ANSI31")))
  (princ))
;; KOLF - столб любой формы (Г-образный и т. п.): первая точка от угла, дальше обход по граням
(defun c:KOLF (/ p e)
  (setvar "CLAYER" "СТЕНЫ")
  (if (setq p (obm:start "Столб любой формы, первый угол"))
    (progn
      (princ "\nОбходи столб по граням: направление мышкой, длину цифрами, Enter. В конце З (или C).")
      (command "_.PLINE" p)
      (while (> (getvar "CMDACTIVE") 0) (command pause))
      (setq e (entlast))
      (if e (obm:hatch e "ANSI31"))))
  (princ))

;;; ---------- 2. СТЕНЫ (сами) ----------
;; SST - построить стены: всё между комнатами + наружные obm:ext, с вырезами под окна и двери
(defun obm:regions (lst / ms r)
  (setq ms (vla-get-ModelSpace (vla-get-ActiveDocument (vlax-get-acad-object))))
  (setq r (vl-catch-all-apply 'vlax-invoke (list ms 'AddRegion lst)))
  (if (vl-catch-all-error-p r) nil r))
(defun obm:unite (regs / u)
  (if regs (progn (setq u (car regs)) (foreach r (cdr regs) (vla-Boolean u 0 r)) u)))
(defun obm:sset (lay / ss i l)
  (setq l '())
  (if (setq ss (ssget "_X" (list '(0 . "LWPOLYLINE") (cons 8 lay))))
    (repeat (setq i (sslength ss)) (setq l (cons (ssname ss (setq i (1- i))) l))))
  l)
(defun c:SST (/ old rooms temp outs ins ops o r big wu iu ou ce h)
  (setq ce (getvar "CMDECHO")) (setvar "CMDECHO" 0)
  (if (setq old (ssget "_X" '((8 . "СТЕНЫ-АВТО")))) (command "_.ERASE" old ""))
  (setq rooms (obm:sset "КОМНАТЫ") outs '() ins '() ops '() temp '())
  (if (not rooms) (princ "\nНет комнат: сначала нарисуй комнаты (KOM / KOMF).")
    (progn
      (foreach e rooms
        (setq o (vlax-ename->vla-object e))
        (setq r (vlax-invoke o 'Offset obm:ext))
        (if (and r (< (vla-get-Area (car r)) (vla-get-Area o))) (progn (foreach x r (vla-delete x)) (setq r (vlax-invoke o 'Offset (- obm:ext)))))
        (if r (setq outs (append outs r) temp (append temp r)))
        (setq big (vla-Copy o) ins (cons big ins) temp (cons big temp)))
      (setq wu (obm:unite (obm:regions outs)))
      (setq iu (obm:unite (obm:regions ins)))
      (foreach e (append (obm:sset "ОКНА") (obm:sset "ДВЕРИ"))
        (setq big (vla-Copy (vlax-ename->vla-object e)) ops (cons big ops) temp (cons big temp)))
      (setq ou (obm:unite (obm:regions ops)))
      (foreach x temp (vl-catch-all-apply 'vla-delete (list x)))
      (if (and wu iu)
        (progn
          (vla-Boolean wu 2 iu)
          (if ou (vla-Boolean wu 2 ou))
          (vla-put-Layer wu "СТЕНЫ-АВТО")
          (setvar "CLAYER" "СТЕНЫ-АВТО")
          (vl-catch-all-apply 'command (list "_.-HATCH" "_P" "ANSI31" 25 0 "_S" (vlax-vla-object->ename wu) "" ""))
          (setvar "CLAYER" "КОМНАТЫ")
          (princ (strcat "\nСтены построены. Наружные - " (itoa obm:ext) " мм (условно, поменять: TOLSH). Поменял комнаты/проёмы - снова SST.")))
        (princ "\nНе получилось построить стены - проверь, что комнаты замкнуты."))))
  (setvar "CMDECHO" ce)
  (princ))
(defun c:TOLSH () (setq obm:ext (obm:askint "Толщина наружных стен, мм" obm:ext)) (princ))

;;; ---------- 3. ОКНА И ДВЕРИ ----------
(defun c:OKN (/ r inf sill top side)
  (setvar "CLAYER" "ОКНА")
  (if (setq r (obm:corners "Окно (первый угол на стене комнаты)"))
    (progn
      (obm:rect (car r) (cadr r) "ОКНА") (setq inf (obm:info (car r) (cadr r)))
      (if (nth 4 inf) (obm:line (obm:p (nth 0 inf) (cadr (nth 7 inf))) (obm:p (nth 2 inf) (cadr (nth 7 inf))) "ОКНА")
                      (obm:line (obm:p (car (nth 7 inf)) (nth 1 inf)) (obm:p (car (nth 7 inf)) (nth 3 inf)) "ОКНА"))
      (setq sill (obm:askint "Подоконник от пола, мм" 900) top (obm:askint "Верх окна от пола, мм" 2400))
      (setq side (getpoint "\nКликни СНАРУЖИ (улица) - туда подпись: "))
      (obm:label inf (strcat "окно " (rtos (nth 5 inf) 2 0) ", пд " (itoa sill) ", верх " (itoa top))
        (if side (if (nth 4 inf) (if (> (cadr side) (cadr (nth 7 inf))) 1 -1) (if (> (car side) (car (nth 7 inf))) 1 -1)) 1) "ОКНА")))
  (princ))

(defun obm:door (lbl defh / r inf x1 y1 x2 y2 hor w hp sp hx hy ox oy face dirn c le oth a1 a2 d h)
  (setvar "CLAYER" "ДВЕРИ")
  (if (setq r (obm:corners (strcat lbl " (первый угол на стене комнаты)")))
    (progn
      (obm:rect (car r) (cadr r) "ДВЕРИ")
      (setq inf (obm:info (car r) (cadr r)) x1 (nth 0 inf) y1 (nth 1 inf) x2 (nth 2 inf) y2 (nth 3 inf) hor (nth 4 inf) w (nth 5 inf))
      (setq hp (getpoint "\nКликни у края проёма, где ПЕТЛИ: ") sp (getpoint "\nКликни в комнату, КУДА открывается: ") dirn 1)
      (if (and hp sp)
        (progn
          (if hor
            (progn (setq hx (if (< (abs (- (car hp) x1)) (abs (- (car hp) x2))) x1 x2) ox (if (= hx x1) x2 x1)
                         face (if (> (cadr sp) (/ (+ y1 y2) 2.0)) y2 y1) dirn (if (= face y2) 1 -1))
                   (setq c (obm:p hx face) le (obm:p hx (+ face (* dirn w))) oth (obm:p ox face)))
            (progn (setq hy (if (< (abs (- (cadr hp) y1)) (abs (- (cadr hp) y2))) y1 y2) oy (if (= hy y1) y2 y1)
                         face (if (> (car sp) (/ (+ x1 x2) 2.0)) x2 x1) dirn (if (= face x2) 1 -1))
                   (setq c (obm:p face hy) le (obm:p (+ face (* dirn w)) hy) oth (obm:p face oy))))
          (obm:line c le "ДВЕРИ")
          (setq a1 (angle c le) a2 (angle c oth) d (rem (+ (- a2 a1) (* 4 pi)) (* 2 pi)))
          (if (equal d (/ pi 2) 0.01) (obm:arc c w a1 a2 "ДВЕРИ") (obm:arc c w a2 a1 "ДВЕРИ"))))
      (setq h (obm:askint "Высота проёма, мм" defh))
      (obm:label inf (strcat lbl " " (rtos w 2 0) ", верх " (itoa h)) (- dirn) "ДВЕРИ")))
  (princ))
(defun c:DVR () (obm:door "дверь" 2100))
(defun c:VHD () (obm:door "вход" 2100))
(defun c:PRM (/ r inf h)
  (setvar "CLAYER" "ДВЕРИ")
  (if (setq r (obm:corners "Проём без двери (первый угол на стене комнаты)"))
    (progn (obm:rect (car r) (cadr r) "ДВЕРИ") (setq inf (obm:info (car r) (cadr r)) h (obm:askint "Высота проёма, мм" 2400))
           (obm:label inf (strcat "проём " (rtos (nth 5 inf) 2 0) ", верх " (itoa h)) 1 "ДВЕРИ")))
  (princ))

;;; ---------- 4. ИНЖЕНЕРИЯ ----------
(defun c:STK (/ c s)
  (setvar "CLAYER" "СТОЯКИ")
  (if (setq c (obm:start "Центр стояка"))
    (progn (obm:circle c 55 "СТОЯКИ") (setq s (obm:askstr "Что за стояк" "К100, ХВС, ГВС"))
           (obm:text (obm:p (car c) (+ (cadr c) 220)) 120 s 0.0 "СТОЯКИ")))
  (princ))
(defun c:KRB (/ r) (setvar "CLAYER" "СТОЯКИ") (if (setq r (obm:corners "Короб / шахта")) (obm:rect (car r) (cadr r) "СТОЯКИ")) (princ))
(defun c:SHT (/ r inf h)
  (setvar "CLAYER" "ЩИТОК")
  (if (setq r (obm:corners "Электрощит (обычно @400,160)"))
    (progn (obm:rect (car r) (cadr r) "ЩИТОК") (setq inf (obm:info (car r) (cadr r)) h (obm:askint "Высота щитка, мм" 1700))
           (obm:text (obm:p (car (nth 7 inf)) (+ (cadr (nth 7 inf)) 300)) 120 (strcat "щиток h " (itoa h)) 0.0 "ЩИТОК")))
  (princ))
(defun c:VNT (/ r inf)
  (setvar "CLAYER" "ВЕНТ")
  (if (setq r (obm:corners "Вентканал / вентилятор"))
    (progn (obm:rect (car r) (cadr r) "ВЕНТ") (setq inf (obm:info (car r) (cadr r)))
           (obm:line (obm:p (nth 0 inf) (nth 1 inf)) (obm:p (nth 2 inf) (nth 3 inf)) "ВЕНТ")
           (obm:line (obm:p (nth 0 inf) (nth 3 inf)) (obm:p (nth 2 inf) (nth 1 inf)) "ВЕНТ")))
  (princ))
(defun c:RAD (/ r inf s)
  (setvar "CLAYER" "РАДИАТОРЫ")
  (if (setq r (obm:corners "Радиатор (вид сверху, например @1200,100)"))
    (progn (obm:rect (car r) (cadr r) "РАДИАТОРЫ") (setq inf (obm:info (car r) (cadr r)))
           (setq s (obm:askstr "Подпись" (strcat "радиатор " (rtos (nth 5 inf) 2 0) ", низ 150"))) (obm:label inf s -1 "РАДИАТОРЫ")))
  (princ))

;;; ---------- ВЫНОСКА (своя, всегда нормального размера) ----------
;; VYN: клик - куда показывает стрелка, клик - где надпись, текст. Стрелка 150, текст 150.
(defun c:VYN (/ p1 p2 s ang a l r b1 b2 dir w)
  (setvar "CLAYER" "РАЗМЕРЫ")
  (while (setq p1 (getpoint "\nВЫНОСКА: куда показывает стрелка (Enter - закончить): "))
    (setq p2 (getpoint p1 "\nГде будет надпись: "))
    (if p2
      (progn
        (setq s (getstring T "\nТекст надписи: "))
        (setq ang (angle p2 p1) l 180.0 w 55.0)
        ;; стрелка - залитый треугольник
        (setq b1 (polar (polar p1 ang (- l)) (+ ang (/ pi 2)) w) b2 (polar (polar p1 ang (- l)) (- ang (/ pi 2)) w))
        (entmake (list '(0 . "SOLID") (cons 8 "РАЗМЕРЫ") (cons 10 p1) (cons 11 b1) (cons 12 b2) (cons 13 b2)))
        (obm:line p1 p2 "РАЗМЕРЫ")
        ;; полка под текстом
        (setq dir (if (>= (car p2) (car p1)) 1 -1) r (+ 200 (* 105 (strlen s))))
        (obm:line p2 (obm:p (+ (car p2) (* dir r)) (cadr p2)) "РАЗМЕРЫ")
        (entmake (list '(0 . "TEXT") (cons 8 "РАЗМЕРЫ") (cons 7 (obm:style)) (cons 10 (obm:p (+ (car p2) (* dir 100)) (+ (cadr p2) 60)))
                       (cons 11 (obm:p (+ (car p2) (* dir 100)) (+ (cadr p2) 60))) '(40 . 150.0) (cons 1 s) '(50 . 0.0)
                       (cons 72 (if (> dir 0) 0 2)) '(73 . 1))))))
  (princ))

;;; ---------- 5. РАЗМЕРЫ И СОХРАНЕНИЕ ----------
(defun c:RAZ () (setvar "CLAYER" "РАЗМЕРЫ") (command "_.DIMLINEAR") (while (> (getvar "CMDACTIVE") 0) (command pause)) (princ))
(defun c:CEP () (setvar "CLAYER" "РАЗМЕРЫ") (command "_.DIMCONTINUE") (while (> (getvar "CMDACTIVE") 0) (command pause)) (princ))
(defun c:SDAT () (initdia) (command "_.SAVEAS") (princ))

;;; ---------- СПРАВКА ----------
(defun c:SPRAVKA ()
  (textscr)
  (princ "\n============ ОБМЕР: ПОРЯДОК И КОМАНДЫ ============")
  (princ "\n 1) КОМНАТЫ (как меряешь, изнутри):")
  (princ "\n    KOM   - прямоугольная: угол + @длина,ширина")
  (princ "\n    KOMF  - любой формы: обход по углам, З - замкнуть")
  (princ "\n    KMT   - СТЕНЫ НАРИСОВАЛ ЛИНИЯМИ? клик внутри комнаты - контур, название, высота сами")
  (princ "\n    Следующая комната: Enter -> угол соседней -> отступ на толщину стены")
  (princ "\n    KOL - столб/колонна прямоугольный, KOLF - столб любой формы (от угла комнаты)")
  (princ "\n 2) ОКНА И ДВЕРИ (в толще стены):")
  (princ "\n    OKN - окно,  DVR - дверь,  VHD - вход,  PRM - проём без двери")
  (princ "\n 3) ИНЖЕНЕРИЯ:  STK - стояк, KRB - короб, SHT - щиток, VNT - вентканал, RAD - радиатор")
  (princ "\n 4) SST - ПОСТРОИТЬ СТЕНЫ (сами, по комнатам). Изменил что-то - снова SST")
  (princ "\n 5) RAZ - размер, CEP - цепочка размеров, VYN - выноска со стрелкой;  SDAT - сохранить DXF")
  (princ "\n    TOLSH - толщина наружных стен (по умолчанию 300)")
  (princ "\n ПРОБЕЛ - повторить последнюю команду. F8 - орто. Esc - отмена.")
  (princ "\n ==================================================")
  (princ))

(c:NASTROYKA)
(princ "\n>>> ОБМЕР v3 загружен. Начни с KOM (комната). Все команды - SPRAVKA")
(princ)
